"""Create a simplified Waveshare ESP32-C6-LCD-1.3-M FreeCAD model.

Overall dimensions and major feature locations follow Waveshare's published
dimension drawing. Small component geometry is intentionally simplified.
"""

from pathlib import Path

import FreeCAD as App
import Part


OUTPUT = Path(__file__).resolve().parent / "src/ESP32-C6-LCD-1.3-M.FCStd"
doc = App.newDocument("ESP32_C6_LCD_1_3_M")
group = doc.addObject("App::DocumentObjectGroup", "BoardAssembly")
group.Label = "Waveshare ESP32-C6-LCD-1.3-M"


def feature(name, label, shape, color):
    obj = doc.addObject("Part::Feature", name)
    obj.Label = label
    obj.Shape = shape
    obj.addProperty("App::PropertyColor", "RenderColor", "Visualization")
    obj.RenderColor = color
    if obj.ViewObject is not None:
        obj.ViewObject.ShapeColor = color
    group.addObject(obj)
    return obj


# Natural board coordinates: X=26.25 mm width, Y=30 mm height, Z=thickness.
feature("PCB", "PCB", Part.makeBox(26.25, 30.0, 1.6), (0.05, 0.22, 0.13))
feature("LCDFrame", "LCD frame", Part.makeBox(26.25, 29.42, 1.7, App.Vector(0, 0, 1.6)), (0.04, 0.04, 0.05))
# The active glass is offset toward the USB-C edge, matching the physical board.
feature("LCDGlass", "LCD glass", Part.makeBox(25.4, 25.4, 0.35, App.Vector(0.425, 4.9, 3.3)), (0.02, 0.06, 0.09))

# Rear-side major components visible in the exploded view.
feature("USB_C", "USB-C connector", Part.makeBox(9.0, 7.0, 3.2, App.Vector(8.625, 23.0, -3.2)), (0.72, 0.74, 0.76))
feature("SDSlot", "MicroSD slot", Part.makeBox(12.0, 9.5, 1.6, App.Vector(7.125, 10.8, -1.6)), (0.60, 0.62, 0.64))
feature("MCU", "ESP32-C6FH4", Part.makeBox(6.0, 6.0, 0.8, App.Vector(10.125, 3.6, -0.8)), (0.12, 0.12, 0.13))
feature("Antenna", "Ceramic antenna", Part.makeBox(5.0, 2.2, 1.2, App.Vector(10.625, 0.4, -1.2)), (0.88, 0.84, 0.70))
feature("ResetButton", "RESET button", Part.makeBox(2.8, 2.0, 1.8, App.Vector(-1.2, 22.0, -1.8)), (0.62, 0.62, 0.64))
feature("BootButton", "BOOT button", Part.makeBox(2.8, 2.0, 1.8, App.Vector(24.65, 22.0, -1.8)), (0.62, 0.62, 0.64))

# SKU 33644 / -M: two six-position 2.54 mm socket rows. They stop
# below the RESET/BOOT button area rather than running the full board height.
header_shape = Part.makeBox(2.4, 15.2, 2.2, App.Vector(0.55, 4.6, -2.2)).fuse(
    Part.makeBox(2.4, 15.2, 2.2, App.Vector(23.30, 4.6, -2.2))
)
feature("HeaderPlastic", "Header plastic", header_shape, (0.06, 0.06, 0.06))
pins = []
for x in (1.75, 24.50):
    for index in range(6):
        pins.append(Part.makeCylinder(0.38, 6.2, App.Vector(x, 5.42 + index * 2.54, -6.2)))
feature("HeaderPins", "Header pins", Part.makeCompound(pins), (0.83, 0.62, 0.18))

# Four M2 mounting-hole accents from the official 22.55 x 26.30 mm pattern.
holes = []
for x in (1.85, 24.40):
    for y in (1.85, 28.15):
        holes.append(Part.makeCylinder(1.0, 0.2, App.Vector(x, y, 1.6)))
feature("MountingHoles", "M2 mounting holes", Part.makeCompound(holes), (0.72, 0.55, 0.18))

doc.recompute()
doc.saveAs(str(OUTPUT))
App.closeDocument(doc.Name)
print(f"Created {OUTPUT}")
