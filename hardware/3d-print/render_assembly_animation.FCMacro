"""Render the SmartHomeCube exploded animation in FreeCAD's real viewport."""

import math
import os
from pathlib import Path

import FreeCAD as App
import FreeCADGui as Gui


MODEL = Path(__file__).resolve().parent / "src/SmartHomeCube.FCStd"
FRAMES = Path("/tmp/smarthomecube-freecad-frames")
FPS = 24
PREVIEW_AMOUNT = os.environ.get("ASSEMBLY_PREVIEW_AMOUNT")
FRAME_COUNT = 1 if PREVIEW_AMOUNT is not None else math.ceil(6.7 * FPS)

# Object name, display color, and final global-Z explosion offset.
ENCLOSURE_PARTS = (
    ("Body", (0.48, 0.40, 0.58), (0.0, 0.0, 0.0)),
    ("Body003", (0.48, 0.40, 0.58), (0.0, 0.0, 65.35)),
    ("Body004", (0.48, 0.40, 0.58), (0.0, 0.0, 80.35)),
    ("Body001", (0.48, 0.40, 0.58), (0.0, 0.0, 95.25)),
)
BOARD_OFFSET = (0.0, 0.0, 49.75)


def smoothstep(value):
    return value * value * (3.0 - 2.0 * value)


def explosion_amount(frame):
    seconds = frame / FPS
    if seconds < 0.6:
        return 0.0
    if seconds < 2.6:
        return smoothstep((seconds - 0.6) / 2.0)
    if seconds < 4.1:
        return 1.0
    if seconds < 6.1:
        return smoothstep((6.1 - seconds) / 2.0)
    return 0.0


FRAMES.mkdir(parents=True, exist_ok=True)
doc = App.openDocument(str(MODEL))
bodies = [doc.getObject(name) for name, _, _ in ENCLOSURE_PARTS]

# The MCU is embedded as one movable App::Part. Its authored Placement is the
# source of truth, so adjustments made in SmartHomeCube.FCStd carry into renders.
board_assembly = doc.getObject("MCU_Assembly")
if board_assembly is None:
    raise RuntimeError("MCU_Assembly is missing; run import_esp32_board.FCMacro")
board_objects = list(board_assembly.Group)

moving_parts = [
    ([bodies[0]], ENCLOSURE_PARTS[0][2]),
    ([bodies[1]], ENCLOSURE_PARTS[1][2]),
    ([board_assembly], BOARD_OFFSET),
    ([bodies[2]], ENCLOSURE_PARTS[2][2]),
    ([bodies[3]], ENCLOSURE_PARTS[3][2]),
]
originals = {obj.Name: obj.Placement.Base for objects, _ in moving_parts for obj in objects}

for obj in doc.Objects:
    obj.ViewObject.Visibility = False
for body, (_, color, _) in zip(bodies, ENCLOSURE_PARTS):
    body.ViewObject.Visibility = True
    body.ViewObject.ShapeColor = color
    body.ViewObject.LineColor = (0.10, 0.10, 0.10)
    body.ViewObject.DisplayMode = "Flat Lines"
    body.ViewObject.LineWidth = 1.0
for obj in board_objects:
    obj.ViewObject.Visibility = True
board_assembly.ViewObject.Visibility = True

view = Gui.activeDocument().activeView()
view.viewTop()
Gui.updateGui()
view.viewAxonometric()
Gui.updateGui()
view.setCornerCrossVisible(False)
try:
    view.setEnabledNaviCube(False)
except AttributeError:
    App.ParamGet("User parameter:BaseApp/Preferences/NaviCube").SetBool("ShowNaviCube", False)

# Fit once to the widest state, then preserve that camera for every frame.
for objects, offset in moving_parts:
    for obj in objects:
        obj.Placement.Base = originals[obj.Name] + App.Vector(*offset)
doc.recompute()
Gui.updateGui()
view.fitAll()
Gui.updateGui()

for frame in range(FRAME_COUNT):
    amount = float(PREVIEW_AMOUNT) if PREVIEW_AMOUNT is not None else explosion_amount(frame)
    for objects, offset in moving_parts:
        for obj in objects:
            obj.Placement.Base = originals[obj.Name] + App.Vector(*offset) * amount
    doc.recompute()
    Gui.updateGui()
    view.saveImage(str(FRAMES / f"frame-{frame:04d}.png"), 1280, 720, "Current")
    print(f"Rendered {frame + 1}/{FRAME_COUNT}")

App.closeDocument(doc.Name)
Gui.getMainWindow().close()
